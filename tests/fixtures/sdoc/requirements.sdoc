[DOCUMENT]
TITLE: Sample Safety Requirements

[REQUIREMENT]
UID: HAZ-001
TITLE: Missing CAM message not detected
STATEMENT: Missing CAM message not detected within timeout period

[REQUIREMENT]
UID: SG-001
TITLE: CAM message timeout detection
STATEMENT: Ensure CAM message reception is monitored with timeout detection
ASIL: ASIL_B
RELATIONS:
- TYPE: Parent
  VALUE: HAZ-001

[REQUIREMENT]
UID: SSR-001
TITLE: Timer scheduling
STATEMENT: cam-service shall schedule a per-event timer that triggers a safety violation if the next event is not received within 1000ms
RELATIONS:
- TYPE: Parent
  VALUE: SG-001

[REQUIREMENT]
UID: SSR-002
TITLE: Timer cancellation
STATEMENT: cam-service shall cancel the timer when a valid event is received
RELATIONS:
- TYPE: Parent
  VALUE: SG-001

[REQUIREMENT]
UID: TC-001
TITLE: Timer scheduling test
STATEMENT: Test that timer is scheduled correctly
RELATIONS:
- TYPE: Parent
  VALUE: SSR-001

[REQUIREMENT]
UID: EVID-001
TITLE: Timer scheduling evidence
STATEMENT: Evidence from timer scheduling tests
RELATIONS:
- TYPE: Parent
  VALUE: TC-001
